[DOCUMENT]
MID: af66c5de119447b58b950dd710d34b8a
TITLE: System Architecture
OPTIONS:
  ENABLE_MID: True

[GRAMMAR]
IMPORT_FROM_FILE: system_architectures.sgra

[TEXT]
MID: 84713f51e27b4ea4bc3242a8e2f1fba7
STATEMENT: >>>
SPDX-License-Identifier: Apache-2.0
<<<

[TEXT]
MID: 0f68a238be874bdcb25a5fbb9f9bcb5c
STATEMENT: >>>
From `SEBoK Wiki Glossary - Architecture <https://sebokwiki.org/wiki/Architecture_(glossary)>`_:

- fundamental concepts or properties of a system in its environment embodied in its elements, relationships, and in the principles of its design and evolution (ISO/IEC/IEEE 2015, Section 4.5)

- The organizational structure of a system or component; the organizational structure of a system and its implementation guidelines. (ISO/IEC 2009, 1)

- Fundamental concepts or properties of a system in its environment embodied in its elements, relationships, and in the principles of its design and evolution. (ISO/IEC 2011, section 3.2)
<<<

[[SECTION]]
MID: 8ecb476dee204236beaca929246ca738
TITLE: Architecture Decision Timeline

[[/SECTION]]

[[SECTION]]
MID: 36617eaf332a4efda48b7b596c66e413
TITLE: Architecture Decisions

[[/SECTION]]

[[SECTION]]
MID: e5076a1d1494497e88e7df3bc0dea09a
TITLE: Logical View

[TEXT]
MID: 671e4f76645344f1b0b35ee9f60b75bb
STATEMENT: >>>
From `4+1 Architectural View Model <https://en.wikipedia.org/wiki/4%2B1_architectural_view_model>`_:

  The logical view is concerned with the functionality that the system provides to end-users. UML diagrams are used to represent the logical view, and include class diagrams, and state diagrams. (Mikko Kontio (2008, July) Architectural manifesto: Designing software architectures, Part 5)
<<<

[TEXT]
MID: d5312fdaf0de42658b9d2287c3eea317
STATEMENT: >>>
.. raw:: html

    <pre class="mermaid">
    ---
    title: Example UML State Diagram
    ---
    stateDiagram-v2

        productMfg: Product Manufacturer
        productMfgWebsite: Product Mfg. Website
        productMfgSupport: Product Mfg. Customer Support
        productSecurityReporting: Product Mfg. <br/> Security Reporting

        state productMfg {
            direction LR

            productMfgWebsite
            productMfgSupport
            productSecurityReporting
        }

        Customer

        Product

    </pre>
<<<

[[/SECTION]]

[[SECTION]]
MID: 2f6357676b7148049baec8001b7d464b
TITLE: Physical View

[TEXT]
MID: 7949001aaf3a413797d5022c40669144
STATEMENT: >>>
From `4+1 Architectural View Model <https://en.wikipedia.org/wiki/4%2B1_architectural_view_model>`_:

  The physical view (aka the deployment view) depicts the system from a system engineer's point of view. It is concerned with the topology of software components on the physical layer as well as the physical connections between these components. UML diagrams used to represent the physical view include the deployment diagram. (Mikko Kontio (2008, July) Architectural manifesto: Designing software architectures, Part 5)
<<<

[TEXT]
MID: 85c0235670da4549884201f91ff364a0
STATEMENT: >>>
.. raw:: html

    <pre class="mermaid">
    ---
    title: Example UML Entity Relationship
    ---
    erDiagram
        CUSTOMER ||--o{ ORDER : places
        ORDER ||--|{ LINE-ITEM : contains
        CUSTOMER }|..|{ DELIVERY-ADDRESS : uses

    </pre>
<<<

[[/SECTION]]

[[SECTION]]
MID: 2fe14357b35b4f0aa9b184fdb1abe15c
TITLE: Concurrency (Process) View

[TEXT]
MID: 5d6d15025b8d486a8aabf215fdf7e40b
STATEMENT: >>>
From `4+1 Architectural View Model <https://en.wikipedia.org/wiki/4%2B1_architectural_view_model>`_:

  The process view deals with the dynamic aspects of the system, explains the system processes and how they communicate, and focuses on the run time behavior of the system. The process view addresses concurrency, distribution, integrator, performance, and scalability, etc. UML diagrams to represent process view include the sequence diagram, communication diagram, activity diagram. (Hui, LM; Leung, CW; Fan, CK; Wong, TN (2004). "Modelling agent-based systems with UML". Proceedings of the Fifth Asia Pacific Industrial Engineering and Management Systems Conference.), (Mikko Kontio (2008, July) Architectural manifesto: Designing software architectures, Part 5)
<<<

[[/SECTION]]

[[SECTION]]
MID: 06283fdaa2da401788553f0cdfa4cbd3
TITLE: Development View

[TEXT]
MID: 652c07a9ceb0481f8819db9c28251c0e
STATEMENT: >>>
From `4+1 Architectural View Model <https://en.wikipedia.org/wiki/4%2B1_architectural_view_model>`_:

  The development view (aka the implementation view) illustrates a system from a programmer's perspective and is concerned with software management. UML Diagrams used to represent the development view include the Package diagram and the Component diagram. (Mikko Kontio (2008, July) Architectural manifesto: Designing software architectures, Part 5)
<<<

[[/SECTION]]

[[SECTION]]
MID: 29a05dd3c9504eb1a78b28a8e1cfc71d
TITLE: Scenarios

[TEXT]
MID: 63b5a1579fa944dc8456deaf2e1d4405
STATEMENT: >>>
From `4+1 Architectural View Model <https://en.wikipedia.org/wiki/4%2B1_architectural_view_model>`_:

  The description of an architecture is illustrated using a small set of use cases, or scenarios, which become a fifth view. The scenarios describe sequences of interactions between objects and between processes. They are used to identify architectural elements and to illustrate and validate the architecture design. They also serve as a starting point for tests of an architecture prototype. This view is also known as the use case view.
<<<

[TEXT]
MID: e0dab2b7af414a92855ef3613ccba1b1
STATEMENT: >>>
.. raw:: html

    <pre class="mermaid">
    ---
    title Example UML Sequence Diagram
    ---
    sequenceDiagram

      %% Set non-default presentation order of participants
      participant A as Alice<br/>Johnson
      participant J as John
      participant C

      C -->> A : Clock chimes

      activate A
      A ->> J : How are you?

      activate J
      note over J : John thinks for a moment

      J ->> A : Fine
      deactivate J
      deactivate A

    </pre>
<<<

[[/SECTION]]
