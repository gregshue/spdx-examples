[DOCUMENT]
MID: 90d096aedd3f4da2bad360c4a22baca9
TITLE: Stakeholders
OPTIONS:
  ENABLE_MID: True

[GRAMMAR]
IMPORT_FROM_FILE: stakeholders.sgra

[TEXT]
MID: 35a45c0a0c5b44dab052f074184f1ac6
STATEMENT: >>>
SPDX-License-Identifier: Apache-2.0
<<<

[TEXT]
MID: afff7b00985542258da8885cfbc9e452
STATEMENT: >>>
From `SEBoK Wiki Glossary - stakeholder <https://sebokwiki.org/wiki/Stakeholder_(glossary)>`_:

- Individual or organization having a right, share, claim, or interest in a system or in its possession of characteristics that meet their needs and expectations (ISO/IEC/IEEE 2015)

- Individual or organization having a right, share, claim, or interest in a system or in its possession of characteristics that meet their needs and expectations; N.B. Stakeholders include, but are not limited to end users, end user organizations, supporters, developers, producers, trainers, maintainers, disposers, acquirers, customers, operators, supplier organizations and regulatory bodies. (ISO/IEC June 2010)

- An individual, team, or organization (or classes thereof) with interests in, or concerns relative to, a system. (ISO/IEC 2007)

- A stakeholder in an organisation is (by definition) any group or individual who can affect or is affected by the achievement of the organisation's objectives. (Freeman 1984)
<<<

[[SECTION]]
MID: 0b181a28b6fe44aebdd68ec2659995ca
TITLE: Manufacturer

[STAKEHOLDER]
MID: 3efd7a67083f4bbb8330264736223e02
UID: STKHLDR-3
STATUS: Draft
TITLE: Marketing

[STAKEHOLDER]
MID: 5b534475caea4f2bb7929596bc1f0e25
UID: STKHLDR-2
STATUS: Draft
TITLE: Project Manager
DESCRIPTION: >>>
Stakeholder overseeing the expenditure of resource to the project.
<<<

[STAKEHOLDER]
MID: 16991861fedf4ea0bc24df024d1164b2
UID: STKHLDR-1
STATUS: Draft
TITLE: Sponsor
DESCRIPTION: >>>
Stakeholder authorizing the expenditure of resources to the project.
<<<

[[/SECTION]]
