[DOCUMENT]
MID: 6a4553bc55b944b9a60c3c760d07ea76
TITLE: Stakeholder Requirements
OPTIONS:
  ENABLE_MID: True

[GRAMMAR]
IMPORT_FROM_FILE: stakeholder_requirements.sgra

[TEXT]
MID: 91e3de0e259e43ecbc9dc4c3987d5f8e
STATEMENT: >>>
SPDX-License-Identifier: Apache-2.0
<<<

[TEXT]
MID: 974887912703457da5e0bc2022cf29d7
STATEMENT: >>>
From `SEBoK Wiki Glossary - stakeholder requirement <https://sebokwiki.org/wiki/Stakeholder_Needs_and_Requirements_(glossary)>`_:

- Stakeholder requirements are transformed from the stakeholder needs to objectively adequate, structured and more formal statements. (ISO/IEC/IEEE 29148, 2018, Section 5.2.3)

- Stakeholder requirements express the intended interaction the system will have with its operational environment and that are the reference against which each resulting operational capability is validated. The stakeholder requirements are defined considering the context of the system of interest with the interoperating systems and enabling systems. This also includes consideration of laws and regulations, environmental restrictions, and ethical values. (ISO/IEC/IEEE 15288, 2023, Section 6.4.2)
<<<

[[SECTION]]
MID: 64ca1a409472407cb81d9e088575070c
TITLE: Manufacturer

[[SECTION]]
MID: 9d271518a6f54faca57afc4c93775c19
TITLE: Engineering

[REQUIREMENT]
MID: 5f3828c9d3954013bba2cdc4f4daa139
UID: STKREQ-54
STATUS: Draft
VERIFICATION: Review
TITLE: System Engineering follows SEBoK 2.12 Wiki
STATEMENT: >>>
The System shall be developed following the best practices described in the Systems Engineering Body of Knowledge (SEBoK) v2.12 Wiki.
<<<
RATIONALE: >>>
The SEBoK Wiki presents the Systems Engineering best practices without cost.
<<<
RELATIONS:
- TYPE: Parent
  VALUE: STKNEED-7
  ROLE: Refines

[REQUIREMENT]
MID: 09d64e339d66456e8f1c375a99350a50
UID: STKREQ-55
STATUS: Draft
VERIFICATION: Review
TITLE: Requirements Written in EARS
STATEMENT: >>>
The System shall express requirements in the Easy Approach to Requirements Syntax (EARS).
<<<
RATIONALE: >>>
[EARS](https://alistairmavin.com/ears/) is a simple syntax already used in the development of certified safety-critical regulated products. The syntax is simple enough for accurate use by non-native English speakers.
<<<
RELATIONS:
- TYPE: Parent
  VALUE: STKNEED-7
  ROLE: Refines

[REQUIREMENT]
MID: 6e3c9a40f74c45ef9bfc557559881820
UID: STKREQ-56
STATUS: Draft
VERIFICATION: Review
TITLE: Architectures Description Follows 4+1 View Model
STATEMENT: >>>
The System shall follow the 4+1 Architectural View Model for describing the architecture(s) within.
<<<
RATIONALE: >>>
A System Engineering best practice is to describe architecture(s) from multiple viewpoints. One of the earliest successful examples of this is the 4+1 Architectural View Model (https://en.wikipedia.org/wiki/4%2B1_architectural_view_model), which provides a high-level breakdown that maps well for describing physical products-with-digital-elements.
<<<
RELATIONS:
- TYPE: Parent
  VALUE: STKNEED-7
  ROLE: Refines

[REQUIREMENT]
MID: 44502658969447bc9cfb7b2d03e2fc91
UID: STKREQ-59
STATUS: Draft
VERIFICATION: Review
TITLE: Architectures Description Includes Decision Statements
STATEMENT: >>>
The System shall include documentation of the architectural decisions.
<<<
RATIONALE: >>>
Engineering staff undergoes significant turnover during a product development and support lifetime. Following documented best practices minimizes the training overhead.
<<<
RELATIONS:
- TYPE: Parent
  VALUE: STKNEED-8
  ROLE: Refines

[REQUIREMENT]
MID: 4567facd0e8341fca6635bd7bd6e8c0f
UID: STKREQ-60
STATUS: Draft
VERIFICATION: Review
TITLE: Architectures Description Includes Decision Timeline
STATEMENT: >>>
The System shall include documentation of the timeline of architectural decisions.
<<<
RATIONALE: >>>
Engineering staff undergoes significant turnover during a product development and support lifetime. Following documented best practices minimizes the training overhead.
<<<
RELATIONS:
- TYPE: Parent
  VALUE: STKNEED-8
  ROLE: Refines

[REQUIREMENT]
MID: d4cc3815c4fb4d0dba80d253a276ca0c
UID: STKREQ-57
STATUS: Draft
VERIFICATION: Review
TITLE: Technical Docs Captured in StrictDoc
STATEMENT: >>>
The System shall capture technical documentation in the open-source software tool StrictDoc.
<<<
RATIONALE: >>>
- StrictDoc is a Free Open-Source Software package.
- StrictDoc has already been used for capturing and tracing technical documentation for a space flight product.
- StrictDoc has already been selected for capturing and tracing requirements for the Linux Foundation's Zephyr Project.
- StrictDoc already has integrated the Free Open-Source Software graph generation tool MermaidUML.
<<<
RELATIONS:
- TYPE: Parent
  VALUE: STKNEED-7
  ROLE: Refines

[REQUIREMENT]
MID: 8de2b35b281d4df190c8b5639e9cce58
UID: STKREQ-58
STATUS: Draft
VERIFICATION: Review
TITLE: StrictDoc configured with MermaidUML enabled
STATEMENT: >>>
The System shall configure StrictDoc such that embedded MermaidUML digrams are rendered.
<<<
RATIONALE: >>>
StrictDoc provides an experimental feature to support embedded MermaidUML diagrams. This feature enables the StrictDoc server to render the diagrams for display on the web pages.
<<<
RELATIONS:
- TYPE: Parent
  VALUE: STKNEED-7
  ROLE: Refines

[[/SECTION]]

[[SECTION]]
MID: ad475da8ced044a696830a504c80cf9c
TITLE: Marketing

[REQUIREMENT]
MID: a76649de31a84f49ba7037db9b938f03
UID: STKREQ-1
STATUS: Draft
VERIFICATION: Analysis
TITLE: Released product conforms to EU CRA
STATEMENT: >>>
Where a consumer electronics product is designated for the European Union market,
the product shall be developed in conformance to the EU Cyber Resilience Act.
<<<
RATIONALE: >>>
EU regulation that comes into full enforcement on 2027 Dec 11.
<<<
RELATIONS:
- TYPE: Parent
  VALUE: STKNEED-1
  ROLE: Refines

[[/SECTION]]

[[SECTION]]
MID: 9d7d78b170a545c586697a6bd8448b47
TITLE: Product Manager

[[/SECTION]]

[[/SECTION]]

[[SECTION]]
MID: 0e9de8b0869d4a07860ea922481da1b3
TITLE: Markets

[[SECTION]]
MID: afe96d9bc00d4a2587fc7dfbbadff847
TITLE: Regulating Authorities

[DOCUMENT_FROM_FILE]
FILE: stkReqs_eu_cra.sdoc

[[/SECTION]]

[[/SECTION]]

[[SECTION]]
MID: 23cc45fd8ca64ec3ba03e6eec4236952
TITLE: Others

[[/SECTION]]
