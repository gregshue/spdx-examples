[DOCUMENT]
MID: 45588823124c47c184e581877e6fd6a8
TITLE: EU Cyber Resilience Act - Requirements
OPTIONS:
  ENABLE_MID: True

[GRAMMAR]
IMPORT_FROM_FILE: @sample_stakeholder_requirements_grammar

[TEXT]
MID: a4963063a5c0464780bc203f80caa9eb
STATEMENT: >>>
SPDX-License-Identifier: Apache-2.0
<<<

[[SECTION]]
MID: a1f540cf6e544602a0f28aa36b9a7b28
TITLE: Annex I - ESSENTIAL CYBERSECURITY REQUIREMENTS

[[SECTION]]
MID: 7c87a7315f744f06b4aaf3834b458e1c
TITLE: Part I Cybersecurity requirements relating to the properties of products with digital elements

[REQUIREMENT]
MID: e316335ca7e1429c98cbbe667a8b82c1
UID: STKREQ-2
STATUS: Draft
VERIFICATION: Review
TITLE: EU CRA Annex I Part I (1)
STATEMENT: >>>
Products with digital elements shall be designed, developed and produced in such a way that they ensure an appropriate level of cybersecurity based on the risks.
<<<
RATIONALE: >>>
Direct quote from https://eur-lex.europa.eu/legal-content/EN/TXT/PDF/?uri=OJ:L_202402847
<<<
RELATIONS:
- TYPE: Parent
  VALUE: STKREQ-1
  ROLE: Refines

[REQUIREMENT]
MID: de89c152d2944c25a9078249d6f3bef0
UID: STKREQ-3
STATUS: Draft
VERIFICATION: Review
TITLE: EU CRA Annex I Part I (2a)
STATEMENT: >>>
On the basis of the cybersecurity risk assessment referred to in Article 13(2) and where applicable, products with digital elements shall be made available on the market without known exploitable vulnerabilities.
<<<
RATIONALE: >>>
Direct quote from https://eur-lex.europa.eu/legal-content/EN/TXT/PDF/?uri=OJ:L_202402847
<<<
RELATIONS:
- TYPE: Parent
  VALUE: STKREQ-1
  ROLE: Refines

[REQUIREMENT]
MID: 4c8123cfe30b440ba028904d69dbb291
UID: STKREQ-4
STATUS: Draft
VERIFICATION: Review
TITLE: EU CRA Annex I Part I (2b)
STATEMENT: >>>
On the basis of the cybersecurity risk assessment referred to in Article 13(2) and where applicable, products with digital elements shall be made available on the market with a secure by default configuration, unless otherwise agreed between manufacturer and business user in relation to a tailor-made product with digital elements, including the possibility to reset the product to its original state.
<<<
RATIONALE: >>>
Direct quote from https://eur-lex.europa.eu/legal-content/EN/TXT/PDF/?uri=OJ:L_202402847
<<<
RELATIONS:
- TYPE: Parent
  VALUE: STKREQ-1
  ROLE: Refines

[REQUIREMENT]
MID: aed3998180fb49ad8982a71121d34100
UID: STKREQ-5
STATUS: Draft
VERIFICATION: Review
TITLE: EU CRA Annex I Part I (2c)
STATEMENT: >>>
On the basis of the cybersecurity risk assessment referred to in Article 13(2) and where applicable, products with digital elements shall ensure that vulnerabilities can be addressed through security updates, including, where applicable, through automatic security updates that are installed within an appropriate timeframe enabled as a default setting, with a clear and easy-to-use opt-out mechanism, through the notification of available updates to users, and the option to temporarily postpone them.
<<<
RATIONALE: >>>
Direct quote from https://eur-lex.europa.eu/legal-content/EN/TXT/PDF/?uri=OJ:L_202402847
<<<
RELATIONS:
- TYPE: Parent
  VALUE: STKREQ-1
  ROLE: Refines

[REQUIREMENT]
MID: 5cb5abd48c174c7fa46c747e55df3a48
UID: STKREQ-6
STATUS: Draft
VERIFICATION: Review
TITLE: EU CRA Annex I Part I (2d)
STATEMENT: >>>
On the basis of the cybersecurity risk assessment referred to in Article 13(2) and where applicable, products with digital elements shall ensure protection from unauthorised access by appropriate control mechanisms, including but not limited to authentication, identity or access management systems, and report on possible unauthorised access.
<<<
RATIONALE: >>>
Direct quote from https://eur-lex.europa.eu/legal-content/EN/TXT/PDF/?uri=OJ:L_202402847
<<<
RELATIONS:
- TYPE: Parent
  VALUE: STKREQ-1
  ROLE: Refines

[REQUIREMENT]
MID: 63031f6137c4460f9e11363a4ccc046e
UID: STKREQ-7
STATUS: Draft
VERIFICATION: Review
TITLE: EU CRA Annex I Part I (2e)
STATEMENT: >>>
On the basis of the cybersecurity risk assessment referred to in Article 13(2) and where applicable, products with digital elements shall protect the confidentiality of stored, transmitted or otherwise processed data, personal or other, such as by encrypting relevant data at rest or in transit by state of the art mechanisms, and by using other technical means.
<<<
RATIONALE: >>>
Direct quote from https://eur-lex.europa.eu/legal-content/EN/TXT/PDF/?uri=OJ:L_202402847
<<<
RELATIONS:
- TYPE: Parent
  VALUE: STKREQ-1
  ROLE: Refines

[REQUIREMENT]
MID: 102c21ff4c224196ba38028f3ad62fd3
UID: STKREQ-8
STATUS: Draft
VERIFICATION: Review
TITLE: EU CRA Annex I Part I (2f)
STATEMENT: >>>
On the basis of the cybersecurity risk assessment referred to in Article 13(2) and where applicable, products with digital elements shall protect the integrity of stored, transmitted or otherwise processed data, personal or other, commands, programs and configuration against any manipulation or modification not authorised by the user, and report on corruptions.
<<<
RATIONALE: >>>
Direct quote from https://eur-lex.europa.eu/legal-content/EN/TXT/PDF/?uri=OJ:L_202402847
<<<
RELATIONS:
- TYPE: Parent
  VALUE: STKREQ-1
  ROLE: Refines

[REQUIREMENT]
MID: 773974ad4dd3431b8e0ca1ece3a61516
UID: STKREQ-9
STATUS: Draft
VERIFICATION: Review
TITLE: EU CRA Annex I Part I (2g)
STATEMENT: >>>
On the basis of the cybersecurity risk assessment referred to in Article 13(2) and where applicable, products with digital elements shall process only data, personal or other, that are adequate, relevant and limited to what is necessary in relation to the intended purpose of the product with digital elements (data minimisation).
<<<
RATIONALE: >>>
Direct quote from https://eur-lex.europa.eu/legal-content/EN/TXT/PDF/?uri=OJ:L_202402847
<<<
RELATIONS:
- TYPE: Parent
  VALUE: STKREQ-1
  ROLE: Refines

[REQUIREMENT]
MID: 75b431ee4500489b88fdb7f2400b2093
UID: STKREQ-10
STATUS: Draft
VERIFICATION: Review
TITLE: EU CRA Annex I Part I (2h)
STATEMENT: >>>
On the basis of the cybersecurity risk assessment referred to in Article 13(2) and where applicable, products with digital elements shall protect the availability of essential and basic functions, also after an incident, including through resilience and mitigation measures against denial-of-service attacks.
<<<
RATIONALE: >>>
Direct quote from https://eur-lex.europa.eu/legal-content/EN/TXT/PDF/?uri=OJ:L_202402847
<<<
RELATIONS:
- TYPE: Parent
  VALUE: STKREQ-1
  ROLE: Refines

[REQUIREMENT]
MID: f3d88193890c40b8bd240c82218c6a70
UID: STKREQ-11
STATUS: Draft
VERIFICATION: Review
TITLE: EU CRA Annex I Part I (2i)
STATEMENT: >>>
On the basis of the cybersecurity risk assessment referred to in Article 13(2) and where applicable, products with digital elements shall minimise the negative impact by the products themselves or connected devices on the availability of services provided by other devices or networks.
<<<
RATIONALE: >>>
Direct quote from https://eur-lex.europa.eu/legal-content/EN/TXT/PDF/?uri=OJ:L_202402847
<<<
RELATIONS:
- TYPE: Parent
  VALUE: STKREQ-1
  ROLE: Refines

[REQUIREMENT]
MID: 6a90d1c2e058426499f990d7c236c8ba
UID: STKREQ-12
STATUS: Draft
VERIFICATION: Review
TITLE: EU CRA Annex I Part I (2j)
STATEMENT: >>>
On the basis of the cybersecurity risk assessment referred to in Article 13(2) and where applicable, products with digital elements shall be designed, developed and produced to limit attack surfaces, including external interfaces.
<<<
RATIONALE: >>>
Direct quote from https://eur-lex.europa.eu/legal-content/EN/TXT/PDF/?uri=OJ:L_202402847
<<<
RELATIONS:
- TYPE: Parent
  VALUE: STKREQ-1
  ROLE: Refines

[REQUIREMENT]
MID: 1c9d567ca06a4690ba86f0dcfbd96150
UID: STKREQ-13
STATUS: Draft
VERIFICATION: Review
TITLE: EU CRA Annex I Part I (2k)
STATEMENT: >>>
On the basis of the cybersecurity risk assessment referred to in Article 13(2) and where applicable, products with digital elements shall be designed, developed and produced to reduce the impact of an incident using appropriate exploitation mitigation mechanisms and techniques.
<<<
RATIONALE: >>>
Direct quote from https://eur-lex.europa.eu/legal-content/EN/TXT/PDF/?uri=OJ:L_202402847
<<<
RELATIONS:
- TYPE: Parent
  VALUE: STKREQ-1
  ROLE: Refines

[REQUIREMENT]
MID: 5538dbea82bd433bad1a63b450446879
UID: STKREQ-14
STATUS: Draft
VERIFICATION: Review
TITLE: EU CRA Annex I Part I (2l)
STATEMENT: >>>
On the basis of the cybersecurity risk assessment referred to in Article 13(2) and where applicable, products with digital elements shall provide security related information by recording and monitoring relevant internal activity, including the access to or modification of data, services or functions, with an opt-out mechanism for the user.
<<<
RATIONALE: >>>
Direct quote from https://eur-lex.europa.eu/legal-content/EN/TXT/PDF/?uri=OJ:L_202402847
<<<
RELATIONS:
- TYPE: Parent
  VALUE: STKREQ-1
  ROLE: Refines

[REQUIREMENT]
MID: 386a68f1b3ae4852b75ecc99966835fb
UID: STKREQ-15
STATUS: Draft
VERIFICATION: Review
TITLE: EU CRA Annex I Part I (2m)
STATEMENT: >>>
On the basis of the cybersecurity risk assessment referred to in Article 13(2) and where applicable, products with digital elements shall provide the possibility for users to securely and easily remove on a permanent basis all data and settings and, where such data can be transferred to other products or systems, ensure that this is done in a secure manner.
<<<
RATIONALE: >>>
Direct quote from https://eur-lex.europa.eu/legal-content/EN/TXT/PDF/?uri=OJ:L_202402847
<<<
RELATIONS:
- TYPE: Parent
  VALUE: STKREQ-1
  ROLE: Refines

[[/SECTION]]

[[SECTION]]
MID: cfdea3f5a0ef4aae92426b8aa900f20b
TITLE: Part II Vulnerability handling requirements

[REQUIREMENT]
MID: 5869c1ee9615463eb239006cc9d010c7
UID: STKREQ-16
STATUS: Draft
VERIFICATION: Review
TITLE: EU CRA Annex I Part II (1)
STATEMENT: >>>
Manufacturers of products with digital elements shall identify and document vulnerabilities and components contained in products with digital elements, including by drawing up a software bill of materials in a commonly used and machine-readable format covering at the very least the top-level dependencies of the products.
<<<
RATIONALE: >>>
Direct quote from https://eur-lex.europa.eu/legal-content/EN/TXT/PDF/?uri=OJ:L_202402847
<<<
RELATIONS:
- TYPE: Parent
  VALUE: STKREQ-1
  ROLE: Refines

[REQUIREMENT]
MID: 2a673eedc0f14ac5819a91be8fb93d1c
UID: STKREQ-17
STATUS: Draft
VERIFICATION: Review
TITLE: EU CRA Annex I Part II (2)(a)
STATEMENT: >>>
Manufacturers of products with digital elements shall in relation to the risks posed to products with digital elements, address and remediate vulnerabilities without delay, including by providing security updates.
<<<
RATIONALE: >>>
Direct quote from https://eur-lex.europa.eu/legal-content/EN/TXT/PDF/?uri=OJ:L_202402847
<<<
RELATIONS:
- TYPE: Parent
  VALUE: STKREQ-1
  ROLE: Refines

[REQUIREMENT]
MID: 9570218144e74d02a459f9189d5675f4
UID: STKREQ-18
STATUS: Draft
VERIFICATION: Review
TITLE: EU CRA Annex I Part II (2)(b)
STATEMENT: >>>
Where technically feasible, Manufacturers of products with digital elements shall provide new security updates separately from functionality updates.
<<<
RATIONALE: >>>
Rephrased quote from https://eur-lex.europa.eu/legal-content/EN/TXT/PDF/?uri=OJ:L_202402847
<<<
RELATIONS:
- TYPE: Parent
  VALUE: STKREQ-1
  ROLE: Refines

[REQUIREMENT]
MID: 20ea525b23de42ec97251389d3eb8d1d
UID: STKREQ-19
STATUS: Draft
VERIFICATION: Review
TITLE: EU CRA Annex I Part II (3)
STATEMENT: >>>
Manufacturers of products with digital elements shall apply effective and regular tests and reviews of the security of the product with digital elements.
<<<
RATIONALE: >>>
Direct quote from https://eur-lex.europa.eu/legal-content/EN/TXT/PDF/?uri=OJ:L_202402847
<<<
RELATIONS:
- TYPE: Parent
  VALUE: STKREQ-1
  ROLE: Refines

[REQUIREMENT]
MID: 5999bd32f3954ce6bcfcfa920c89cfce
UID: STKREQ-20
STATUS: Draft
VERIFICATION: Review
TITLE: EU CRA Annex I Part II (4)(a)
STATEMENT: >>>
Once a security update has been made available, Manufacturers of products with digital elements shall share and publicly disclose information about fixed vulnerabilities, including a description of the vulnerabilities, information allowing users to identify the product with digital elements affected, the impacts of the vulnerabilities, their severity and clear and accessible information helping users to remediate the vulnerabilities.
<<<
RATIONALE: >>>
Reordered quote from https://eur-lex.europa.eu/legal-content/EN/TXT/PDF/?uri=OJ:L_202402847
<<<
RELATIONS:
- TYPE: Parent
  VALUE: STKREQ-1
  ROLE: Refines

[REQUIREMENT]
MID: 63117677fb1c40af9ea2231f8d6d6dfe
UID: STKREQ-21
STATUS: Draft
VERIFICATION: Review
TITLE: EU CRA Annex I Part II (4)(b)
STATEMENT: >>>
Where Manufacturers of products with digital elements consider the security risks of publication to outweigh the security benefits,
said Manufacturers shall duly justify for this case any delay in making public information regarding a fixed vulnerability until after users have
been given the possibility to apply the relevant patch.
<<<
RATIONALE: >>>
Reworded statement from https://eur-lex.europa.eu/legal-content/EN/TXT/PDF/?uri=OJ:L_202402847 into a requirement.
<<<
RELATIONS:
- TYPE: Parent
  VALUE: STKREQ-1
  ROLE: Refines

[REQUIREMENT]
MID: e3949ba873b646a487f3e9272f2f9d4f
UID: STKREQ-22
STATUS: Draft
VERIFICATION: Review
TITLE: EU CRA Annex I Part II (5)
STATEMENT: >>>
Manufacturers of products with digital elements shall put in place and enforce a policy on coordinated vulnerability disclosure.
<<<
RATIONALE: >>>
Direct quote from https://eur-lex.europa.eu/legal-content/EN/TXT/PDF/?uri=OJ:L_202402847
<<<
RELATIONS:
- TYPE: Parent
  VALUE: STKREQ-1
  ROLE: Refines

[REQUIREMENT]
MID: d19ee2a5ef83478ea7709cb329bde3e3
UID: STKREQ-23
STATUS: Draft
VERIFICATION: Review
TITLE: EU CRA Annex I Part II (6)
STATEMENT: >>>
Manufacturers of products with digital elements shall take measures to facilitate the sharing of information about potential vulnerabilities in their product with digital elements as well as in third-party components contained in that product, including by providing a contact address for the reporting of the vulnerabilities discovered in the product with digital elements.
<<<
RATIONALE: >>>
Direct quote from https://eur-lex.europa.eu/legal-content/EN/TXT/PDF/?uri=OJ:L_202402847
<<<
RELATIONS:
- TYPE: Parent
  VALUE: STKREQ-1
  ROLE: Refines

[REQUIREMENT]
MID: 9961a0d5f6e24aa2a254a159f36d93b4
UID: STKREQ-24
STATUS: Draft
VERIFICATION: Review
TITLE: EU CRA Annex I Part II (7)
STATEMENT: >>>
Manufacturers of products with digital elements shall provide for mechanisms to securely distribute updates for products with digital elements to ensure that vulnerabilities are fixed or mitigated in a timely manner and, where applicable for security updates, in an automatic manner.
<<<
RATIONALE: >>>
Direct quote from https://eur-lex.europa.eu/legal-content/EN/TXT/PDF/?uri=OJ:L_202402847
<<<
RELATIONS:
- TYPE: Parent
  VALUE: STKREQ-1
  ROLE: Refines

[REQUIREMENT]
MID: 46b5bee525b042cb8bc9df84aee633a3
UID: STKREQ-25
STATUS: Draft
VERIFICATION: Review
TITLE: EU CRA Annex I Part II (8)
STATEMENT: >>>
Manufacturers of products with digital elements shall ensure that, where security updates are available to address identified security issues, they are disseminated without delay and, unless otherwise agreed between a manufacturer and a business user in relation to a tailor-made product with digital elements, free of charge, accompanied by advisory messages providing users with the relevant information, including on potential action to be taken.
<<<
RATIONALE: >>>
Direct quote from https://eur-lex.europa.eu/legal-content/EN/TXT/PDF/?uri=OJ:L_202402847
<<<
RELATIONS:
- TYPE: Parent
  VALUE: STKREQ-1
  ROLE: Refines

[[/SECTION]]

[[/SECTION]]

[[SECTION]]
MID: dc789251b3c3434f8860298bbca599a4
TITLE: Annex II - INFORMATION AND INSTRUCTIONS TO THE USER

[REQUIREMENT]
MID: 230e5744173f4cc7855f74335dc2e75c
UID: STKREQ-26
STATUS: Draft
VERIFICATION: Review
TITLE: EU CRA Annex II (1)(a)
STATEMENT: >>>
The product with digital elements shall be accompanied by the name, registered trade name or registered trademark of the manufacturer.
<<<
RATIONALE: >>>
Direct quote from https://eur-lex.europa.eu/legal-content/EN/TXT/PDF/?uri=OJ:L_202402847
<<<
RELATIONS:
- TYPE: Parent
  VALUE: STKREQ-1
  ROLE: Refines

[REQUIREMENT]
MID: 875167f7449b4f7ca0d63a12abc93e41
UID: STKREQ-27
STATUS: Draft
VERIFICATION: Review
TITLE: EU CRA Annex II (1)(b)
STATEMENT: >>>
The product with digital elements shall be accompanied by the postal address at which the manufacturer can be contacted.
<<<
RATIONALE: >>>
Direct quote from https://eur-lex.europa.eu/legal-content/EN/TXT/PDF/?uri=OJ:L_202402847
<<<
RELATIONS:
- TYPE: Parent
  VALUE: STKREQ-1
  ROLE: Refines

[REQUIREMENT]
MID: 2ddb1783ffab46c8a3c308128a516996
UID: STKREQ-28
STATUS: Draft
VERIFICATION: Review
TITLE: EU CRA Annex II (1)(c)
STATEMENT: >>>
The product with digital elements shall be accompanied by the email address or other digital contact at which the manufacturer can be contacted.
<<<
RATIONALE: >>>
Direct quote from https://eur-lex.europa.eu/legal-content/EN/TXT/PDF/?uri=OJ:L_202402847
<<<
RELATIONS:
- TYPE: Parent
  VALUE: STKREQ-1
  ROLE: Refines

[REQUIREMENT]
MID: afeba84ba543490b931215b0c1ac1cef
UID: STKREQ-29
STATUS: Draft
VERIFICATION: Review
TITLE: EU CRA Annex II (1)(d)
STATEMENT: >>>
The product with digital elements shall be accompanied by, where available, the website at which the manufacturer can be contacted.
<<<
RATIONALE: >>>
Direct quote from https://eur-lex.europa.eu/legal-content/EN/TXT/PDF/?uri=OJ:L_202402847
<<<
RELATIONS:
- TYPE: Parent
  VALUE: STKREQ-1
  ROLE: Refines

[[/SECTION]]
